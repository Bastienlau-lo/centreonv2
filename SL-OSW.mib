-- *****************************************************************
-- Optical Switch Module MIB
-- *****************************************************************

SL-OSW-MIB DEFINITIONS ::= BEGIN

IMPORTS
	MODULE-IDENTITY, OBJECT-TYPE, Integer32,
	NOTIFICATION-TYPE, Gauge32, 
	Counter64     	                    FROM SNMPv2-SMI
	DisplayString, TruthValue,
	DateAndTime							FROM SNMPv2-TC
	MODULE-COMPLIANCE, OBJECT-GROUP,
	NOTIFICATION-GROUP                  FROM SNMPv2-CONF
	InterfaceIndex		               	FROM IF-MIB
	slService				      		FROM SL-NE-MIB;

slOSW MODULE-IDENTITY
	LAST-UPDATED "0508171200Z"   -- 17 Jan. 2005  12:00:00 EST
	ORGANIZATION "NOKIA"
	CONTACT-INFO
		"jeff.donnelly@nokia.com"
	DESCRIPTION
		"This MIB module describes the Optical Switch"
	::= { slService 17 }

-- The OSW MIB consists of the following groups:
--    Configuration
--    Traps

slOSWConfig		OBJECT IDENTIFIER ::= { slOSW 1 }
slOSWPm	 		OBJECT IDENTIFIER ::= { slOSW 2 }
slOSWTraps 		OBJECT IDENTIFIER ::= { slOSW 3 }


-- Textual Conventions



--
-- The OSW Ports Configuration Table
--

slOSWPortConfigTable OBJECT-TYPE
	SYNTAX  SEQUENCE OF SlOSWPortConfigEntry
	MAX-ACCESS  		not-accessible
	STATUS  			current
	DESCRIPTION
		"The OSW Port Configuration table."
	::= { slOSWConfig 1 }

slOSWPortConfigEntry OBJECT-TYPE
	SYNTAX  SlOSWPortConfigEntry
	MAX-ACCESS  not-accessible
	STATUS  current
	DESCRIPTION
		"An entry in the OSW ports configuration table."
	INDEX   { slOSWPortConfigLineIndex }
	::= { slOSWPortConfigTable 1 }

SlOSWPortConfigEntry ::=
	SEQUENCE {
		slOSWPortConfigLineIndex        		InterfaceIndex,
		slOSWPortConfigInPowerLevel				INTEGER,
		slOSWPortConfigLosThreshold				INTEGER,
		slOSWPortConfigDirection				INTEGER
	}

slOSWPortConfigLineIndex OBJECT-TYPE
	SYNTAX  	InterfaceIndex
	MAX-ACCESS  read-only
	STATUS  	current
	DESCRIPTION
		"The ifIndex of the port."
	::= { slOSWPortConfigEntry 1 }

slOSWPortConfigInPowerLevel OBJECT-TYPE
	SYNTAX      INTEGER
    MAX-ACCESS  read-only
    STATUS      current
    DESCRIPTION 
    	"The Input Power Level of the port."
    ::= { slOSWPortConfigEntry 2 }

slOSWPortConfigLosThreshold OBJECT-TYPE
    SYNTAX      INTEGER (0..65535)
    MAX-ACCESS  read-write
    STATUS      current
    DESCRIPTION
		"Configured threshold value for LOS detection of the optical switch port.
		The value given in 0.1 dBm units. The range starts with -50.0 dBm."
	::= { slOSWPortConfigEntry 3 }

slOSWPortConfigDirection 	OBJECT-TYPE
	SYNTAX      	INTEGER {
		bidirectional(1),		-- optical switch is bidierctional (default)
		unidirectionalTx(2),	-- optical switch is TX only
		unidirectionalRx(3)		-- optical switch is RX only
	}
	MAX-ACCESS  	read-write
	STATUS      	current
	DESCRIPTION
		"This object specifies the direction of the optical switch."
	::= { slOSWPortConfigEntry 4 }

-- 
-- OSW Traps
-- 


END
