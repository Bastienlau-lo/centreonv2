-- *****************************************************************
-- DCM MIB
-- *****************************************************************

SL-DCM-MIB DEFINITIONS ::= BEGIN

IMPORTS
	MODULE-IDENTITY, OBJECT-TYPE,
	NOTIFICATION-TYPE, Integer32, TimeTicks
					 			     	FROM SNMPv2-SMI
	DisplayString, TruthValue, 
	TimeStamp					  		FROM SNMPv2-TC
    SnmpAdminString						FROM SNMP-FRAMEWORK-MIB
    MODULE-COMPLIANCE, OBJECT-GROUP,
	NOTIFICATION-GROUP                  FROM SNMPv2-CONF
	InterfaceIndex		               	FROM IF-MIB
	PerfCurrentCount, PerfIntervalCount,
	PerfTotalCount                      FROM PerfHist-TC-MIB
	CleiCode							FROM SL-ENTITY-MIB
	sitelight				      		FROM SL-NE-MIB;

slDcm MODULE-IDENTITY
	LAST-UPDATED "201206120000Z"
	ORGANIZATION "NOKIA"
	CONTACT-INFO
		"jeff.donnelly@nokia.com"
	DESCRIPTION
		"This MIB module describes the DCM modules"
	::= { sitelight 14 }

--	The DCM MIB consists of the following groups:
--	DCM Table


-- ----------------------------------------------------
--
-- The DCM Module Table
--
-- ----------------------------------------------------

dcmTable OBJECT-TYPE
	SYNTAX  SEQUENCE OF DcmEntry
	MAX-ACCESS  		not-accessible
	STATUS  			current
	DESCRIPTION
		"The DCM table."
	::= { slDcm 1 }

dcmEntry OBJECT-TYPE
	SYNTAX  DcmEntry
	MAX-ACCESS  not-accessible
	STATUS  current
	DESCRIPTION
		"An entry in the DCM table."
	INDEX   { dcmIndex }
	::= { dcmTable 1 }

DcmEntry ::=
	SEQUENCE {
		dcmIndex				InterfaceIndex,
		dcmRange				INTEGER,
		dcmSpacing				INTEGER,
		dcmTemperature			INTEGER,
		dcmIsActive				TruthValue,
		dcmFiberCoefficient		INTEGER,
		dcmMinDispersion		INTEGER,
		dcmMaxDispersion		INTEGER
	}

dcmIndex OBJECT-TYPE
	SYNTAX  	InterfaceIndex
	MAX-ACCESS  read-only
	STATUS  	current
	DESCRIPTION
		"The interface index of the DCM (Type=195; Port=216)."
	::= { dcmEntry 1 }

dcmRange OBJECT-TYPE
	SYNTAX  INTEGER
	MAX-ACCESS  	read-write
	STATUS  		current
	DESCRIPTION
		"The range in dispersion units (ps/nm).
		 The object is given by the user in km units and the value is translated to dispersion units and wrotten to the DCM."
	::= { dcmEntry 2 }

dcmSpacing OBJECT-TYPE
	SYNTAX  INTEGER
	MAX-ACCESS  	read-only
	STATUS  		current
	DESCRIPTION
		"The spacing between two adjacent optical channels in GHz units."
	::= { dcmEntry 3 }

dcmTemperature OBJECT-TYPE
	SYNTAX  INTEGER
	MAX-ACCESS  	read-only
	STATUS  		current
	DESCRIPTION
		"This object is applicable only for active DCM modules.
		The temperature is encoded as a signed two’s complement value in ºC, 
		yielding a total range of –128C to +127ºC"
	::= { dcmEntry 4 }

dcmIsActive OBJECT-TYPE
	SYNTAX  TruthValue
	MAX-ACCESS  	read-only
	STATUS  		current
	DESCRIPTION
		"Indicate if the DCM module is active.
		 The value true if the value of the DCM range in the SEEP is 1."
	::= { dcmEntry 5 }

dcmFiberCoefficient OBJECT-TYPE
	SYNTAX  INTEGER 
	MAX-ACCESS  	read-write
	STATUS  		current
	DESCRIPTION
		"The fiber chromatic dispersion coefficient.
		 For example the chromatic dispersion coefficient value for G.652 fiber is 17 ps/(nm km).
		 For G.655 is 6 ps/(nm km)
		 For G.656 is 14 ps/(nm km)
		 The default value is 17."
	::= { dcmEntry 6 }

dcmMinDispersion OBJECT-TYPE
	SYNTAX  INTEGER 
	MAX-ACCESS  	read-only
	STATUS  		current
	DESCRIPTION
		"The minimal dispersion supported by the DCM module.
		Example -1350 ps/nm"
	::= { dcmEntry 7 }

dcmMaxDispersion OBJECT-TYPE
	SYNTAX  INTEGER 
	MAX-ACCESS  	read-only
	STATUS  		current
	DESCRIPTION
		"The maximal dispersion supported by the DCM module.
		Example -350 ps/nm"
	::= { dcmEntry 8 }

END
